package AgentControl {
    part def Context {
        doc /* Command-line argument parser and I/O owner for one tool invocation. */

        comment sourceRef /* Source: src/DemaConsulting.AgentControl/Cli/Context.cs */
        comment testRef /* Test: test/DemaConsulting.AgentControl.Tests/Cli/ContextTests.cs */
        comment designRef /* Design: docs/design/agent-control/cli/context.md */
        comment verificationRef /* Verification: docs/verification/agent-control/cli/context.md */
        comment reqRef /* Requirements: docs/reqstream/agent-control/cli/context.yaml */
    }
}
