package AgentControl {
    part def Validation {
        doc /* Orchestrates the self-validation test suite and reports pass/fail results. */

        comment sourceRef /* Source: src/DemaConsulting.AgentControl/SelfTest/Validation.cs */
        comment testRef /* Test: test/DemaConsulting.AgentControl.Tests/SelfTest/ValidationTests.cs */
        comment designRef /* Design: docs/design/agent-control/self-test/validation.md */
        comment verificationRef /* Verification: docs/verification/agent-control/self-test/validation.md */
        comment reqRef /* Requirements: docs/reqstream/agent-control/self-test/validation.yaml */
    }
}
